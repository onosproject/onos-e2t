-- **************************************************************
--
-- Elementary Procedure definitions
-- Derived from 3GPP 38.413 v15.4.0 NGAP
-- **************************************************************

E2AP-PDU-VONE-Descriptions {
iso(1) identified-organization(3) dod(6) internet(1) private(4) enterprise(1) 53148 e2(1) version1 (1) e2ap(1) e2ap-PDU-Descriptions (0) }

DEFINITIONS AUTOMATIC TAGS ::= 

BEGIN

-- **************************************************************
--
-- IE parameter types from other modules.
--
-- **************************************************************

IMPORTS
	CriticalityVone,
	ProcedureCodeVone
FROM E2AP-CommonDataTypes



	E2connectionUpdateVone,
	E2connectionUpdateAcknowledgeVone,
	E2connectionUpdateFailureVone,
	E2nodeConfigurationUpdateVone,
	E2nodeConfigurationUpdateAcknowledgeVone,
	E2nodeConfigurationUpdateFailureVone,
	E2setupFailureVone,
	E2setupRequestVone,
	E2setupResponseVone,
	ErrorIndicationVone,
	ResetRequestVone,
	ResetResponseVone,
	RICcontrolAcknowledgeVone,
	RICcontrolFailureVone,
	RICcontrolRequestVone,
	RICindicationVone,
	RICserviceQueryVone,
	RICserviceUpdateVone,
	RICserviceUpdateAcknowledgeVone,
	RICserviceUpdateFailureVone,
	RICsubscriptionFailureVone,
	RICsubscriptionRequestVone,
	RICsubscriptionResponseVone,
	RICsubscriptionDeleteFailureVone,
	RICsubscriptionDeleteRequestVone,
	RICsubscriptionDeleteResponseVone
FROM E2AP-PDU-VONE-Contents

	id-E2connectionUpdateVone,
	id-E2nodeConfigurationUpdateVone,
	id-E2setupVone,
	id-ErrorIndicationVone,
	id-ResetVone,
	id-RICcontrolVone,
	id-RICindicationVone,
	id-RICserviceQueryVone,
	id-RICserviceUpdateVone,
	id-RICsubscriptionVone,
	id-RICsubscriptionDeleteVone
FROM E2AP-Constants;

-- **************************************************************
--
-- Interface Elementary Procedure Class
--
-- **************************************************************

E2AP-ELEMENTARY-PROCEDURE-VONE ::= CLASS {
	&InitiatingMessageVone										,
	&SuccessfulOutcomeVone							OPTIONAL	,
	&UnsuccessfulOutcomeVone						OPTIONAL	,
	&procedureCode				ProcedureCodeVone	UNIQUE	,
	&criticality				CriticalityVone		DEFAULT ignore
}

WITH SYNTAX {
	INITIATING MESSAGE			&InitiatingMessageVone
	[SUCCESSFUL OUTCOME			&SuccessfulOutcomeVone]
	[UNSUCCESSFUL OUTCOME		&UnsuccessfulOutcomeVone]
	PROCEDURE CODE				&procedureCode
	[CRITICALITY				&criticality]
}

-- **************************************************************
--
-- Interface PDU Definition
--
-- **************************************************************

E2AP-PDU-VONE ::= CHOICE {
	initiatingMessage			InitiatingMessageVone,
	successfulOutcome			SuccessfulOutcomeVone,
	unsuccessfulOutcome			UnsuccessfulOutcomeVone,
	...
}

InitiatingMessageVone ::= SEQUENCE {
	procedureCode	E2AP-ELEMENTARY-PROCEDURE-VONE.&procedureCode		({E2AP-ELEMENTARY-PROCEDURES-VONE}),
	criticality		E2AP-ELEMENTARY-PROCEDURE-VONE.&criticality			({E2AP-ELEMENTARY-PROCEDURES-VONE}{@procedureCode}),
	value			E2AP-ELEMENTARY-PROCEDURE-VONE.&InitiatingMessageVone	({E2AP-ELEMENTARY-PROCEDURES-VONE}{@procedureCode})
}

SuccessfulOutcomeVone ::= SEQUENCE {
	procedureCode	E2AP-ELEMENTARY-PROCEDURE-VONE.&procedureCode		({E2AP-ELEMENTARY-PROCEDURES-VONE}),
	criticality		E2AP-ELEMENTARY-PROCEDURE-VONE.&criticality			({E2AP-ELEMENTARY-PROCEDURES-VONE}{@procedureCode}),
	value			E2AP-ELEMENTARY-PROCEDURE-VONE.&SuccessfulOutcomeVone	({E2AP-ELEMENTARY-PROCEDURES-VONE}{@procedureCode})
}

UnsuccessfulOutcomeVone ::= SEQUENCE {
	procedureCode	E2AP-ELEMENTARY-PROCEDURE-VONE.&procedureCode		({E2AP-ELEMENTARY-PROCEDURES-VONE}),
	criticality		E2AP-ELEMENTARY-PROCEDURE-VONE.&criticality			({E2AP-ELEMENTARY-PROCEDURES-VONE}{@procedureCode}),
	value			E2AP-ELEMENTARY-PROCEDURE-VONE.&UnsuccessfulOutcomeVone	({E2AP-ELEMENTARY-PROCEDURES-VONE}{@procedureCode})
}

-- **************************************************************
--
-- Interface Elementary Procedure List
--
-- **************************************************************

E2AP-ELEMENTARY-PROCEDURES-VONE E2AP-ELEMENTARY-PROCEDURE-VONE ::= {
	E2AP-ELEMENTARY-PROCEDURES-VONE-CLASS-1					|
	E2AP-ELEMENTARY-PROCEDURES-VONE-CLASS-2,
	...
}

E2AP-ELEMENTARY-PROCEDURES-VONE-CLASS-1 E2AP-ELEMENTARY-PROCEDURE-VONE ::= {
	ricSubscriptionVone										|
	ricSubscriptionDeleteVone								|
	ricServiceUpdateVone									|
	ricControlVone											|
	e2setupVone												|
	e2nodeConfigurationUpdateVone							|
	e2connectionUpdateVone									|
	resetVone,
	...
}

E2AP-ELEMENTARY-PROCEDURES-VONE-CLASS-2 E2AP-ELEMENTARY-PROCEDURE-VONE ::= {
	ricIndicationVone										|
	ricServiceQueryVone										|
	errorIndicationVone,	
	...
}

-- **************************************************************
--
-- Interface Elementary Procedures
--
-- **************************************************************

-- New for v01.01
e2connectionUpdateVone	E2AP-ELEMENTARY-PROCEDURE-VONE ::= {
	INITIATING MESSAGE		E2connectionUpdateVone
	SUCCESSFUL OUTCOME		E2connectionUpdateAcknowledgeVone
	UNSUCCESSFUL OUTCOME	E2connectionUpdateFailureVone
	PROCEDURE CODE			id-E2connectionUpdateVone
	CRITICALITY				reject
}

e2nodeConfigurationUpdateVone	E2AP-ELEMENTARY-PROCEDURE-VONE ::= {
	INITIATING MESSAGE		E2nodeConfigurationUpdateVone
	SUCCESSFUL OUTCOME		E2nodeConfigurationUpdateAcknowledgeVone
	UNSUCCESSFUL OUTCOME	E2nodeConfigurationUpdateFailureVone
	PROCEDURE CODE			id-E2nodeConfigurationUpdateVone
	CRITICALITY				reject
}

e2setupVone	E2AP-ELEMENTARY-PROCEDURE-VONE ::= {
	INITIATING MESSAGE		E2setupRequestVone
	SUCCESSFUL OUTCOME		E2setupResponseVone
	UNSUCCESSFUL OUTCOME	E2setupFailureVone
	PROCEDURE CODE			id-E2setupVone
	CRITICALITY				reject
}

errorIndicationVone E2AP-ELEMENTARY-PROCEDURE-VONE ::= {
	INITIATING MESSAGE		ErrorIndicationVone
	PROCEDURE CODE			id-ErrorIndicationVone
	CRITICALITY				ignore
}

resetVone	E2AP-ELEMENTARY-PROCEDURE-VONE ::= {
	INITIATING MESSAGE		ResetRequestVone
	SUCCESSFUL OUTCOME		ResetResponseVone
	PROCEDURE CODE			id-ResetVone
	CRITICALITY				reject
}

ricControlVone E2AP-ELEMENTARY-PROCEDURE-VONE ::= {
	INITIATING MESSAGE		RICcontrolRequestVone
	SUCCESSFUL OUTCOME		RICcontrolAcknowledgeVone
	UNSUCCESSFUL OUTCOME	RICcontrolFailureVone
	PROCEDURE CODE			id-RICcontrolVone
	CRITICALITY				reject
}

ricIndicationVone E2AP-ELEMENTARY-PROCEDURE-VONE ::= {
	INITIATING MESSAGE		RICindicationVone
	PROCEDURE CODE			id-RICindicationVone
	CRITICALITY				ignore
}

ricServiceQueryVone E2AP-ELEMENTARY-PROCEDURE-VONE ::= {
	INITIATING MESSAGE		RICserviceQueryVone
	PROCEDURE CODE			id-RICserviceQueryVone
	CRITICALITY				ignore
}

ricServiceUpdateVone E2AP-ELEMENTARY-PROCEDURE-VONE ::= {
	INITIATING MESSAGE		RICserviceUpdateVone
	SUCCESSFUL OUTCOME		RICserviceUpdateAcknowledgeVone
	UNSUCCESSFUL OUTCOME	RICserviceUpdateFailureVone
	PROCEDURE CODE			id-RICserviceUpdateVone
	CRITICALITY				reject
}

ricSubscriptionVone E2AP-ELEMENTARY-PROCEDURE-VONE ::= {
	INITIATING MESSAGE		RICsubscriptionRequestVone
	SUCCESSFUL OUTCOME		RICsubscriptionResponseVone
	UNSUCCESSFUL OUTCOME	RICsubscriptionFailureVone
	PROCEDURE CODE			id-RICsubscriptionVone
	CRITICALITY				reject
}

ricSubscriptionDeleteVone E2AP-ELEMENTARY-PROCEDURE-VONE ::= {
	INITIATING MESSAGE		RICsubscriptionDeleteRequestVone
	SUCCESSFUL OUTCOME		RICsubscriptionDeleteResponseVone
	UNSUCCESSFUL OUTCOME	RICsubscriptionDeleteFailureVone
	PROCEDURE CODE			id-RICsubscriptionDeleteVone
	CRITICALITY				reject
}


END
-- **************************************************************
--
-- PDU definitions for E2AP
-- Derived from 3GPP 38.413 v15.4.0 NGAP
-- 
-- **************************************************************

E2AP-PDU-VONE-Contents {
iso(1) identified-organization(3) dod(6) internet(1) private(4) enterprise(1) 53148 e2(1) version1 (1) e2ap(1) e2ap-PDU-Contents (1) }

DEFINITIONS AUTOMATIC TAGS ::= 

BEGIN

-- **************************************************************
--
-- IE parameter types from other modules.
--
-- **************************************************************

IMPORTS
	CauseVone,
	CriticalityDiagnosticsVone,
	E2nodeComponentConfigUpdateVone,
	E2nodeComponentConfigUpdateAckVone,
	E2nodeComponentIDVone,
	E2nodeComponentTypeVone,
	GlobalE2node-IDVone,
	GlobalRIC-IDVone,
	RANfunctionDefinitionVone,
	RANfunctionIDVone,
	RANfunctionOIDVone,
	RANfunctionRevisionVone,
	RICactionDefinitionVone,
	RICactionIDVone,
	RICactionTypeVone,
	RICcallProcessIDVone,
	RICcontrolAckRequestVone,
	RICcontrolHeaderVone,
	RICcontrolMessageVone,
	RICcontrolOutcomeVone,
	RICcontrolStatusVone,
	RICeventTriggerDefinitionVone,
	RICindicationHeaderVone,
	RICindicationMessageVone,
	RICindicationSNVone,
	RICindicationTypeVone,
	RICrequestIDVone,
	RICsubsequentActionVone,
	TimeToWaitVone,
	TNLinformationVone,
	TNLusageVone
FROM E2AP-IEs

	ProtocolIE-Container{},
	ProtocolIE-ContainerList{},
	ProtocolIE-SingleContainer{},
	E2AP-PROTOCOL-IES-VONE,
	E2AP-PROTOCOL-IES-VONE-PAIR
FROM E2AP-Containers

	id-CauseVone,
	id-CriticalityDiagnosticsVone,
	id-E2connectionSetup,
	id-E2connectionSetupFailed,
	id-E2connectionSetupFailed-Item-Vone,
	id-E2connectionFailed-Item,
	id-E2connectionUpdateVone-Item,
	id-E2connectionUpdateAdd,
	id-E2connectionUpdateModify,
	id-E2connectionUpdateRemove,
	id-E2connectionUpdateRemove-Item-Vone,
	id-E2nodeComponentConfigUpdateVone,
	id-E2nodeComponentConfigUpdateVone-Item,
	id-E2nodeComponentConfigUpdateAckVone,
	id-E2nodeComponentConfigUpdateAckVone-Item,
	id-GlobalE2node-IDVone,
	id-GlobalRIC-IDVone,
	id-RANfunctionIDVone,
	id-RANfunctionIDVone-Item,
	id-RANfunctionIEcause-Item,
	id-RANfunction-Item-Vone,
	id-RANfunctionsAccepted,
	id-RANfunctionsAdded,
	id-RANfunctionsDeleted,
	id-RANfunctionsModified,
	id-RANfunctionsRejected,
	id-RICaction-Admitted-Item-Vone,
	id-RICactionIDVone,
	id-RICaction-NotAdmitted-Item-Vone,
	id-RICactions-Admitted,
	id-RICactions-NotAdmitted,
	id-RICaction-ToBeSetup-Item-Vone,
	id-RICcallProcessIDVone,
	id-RICcontrolAckRequestVone,
	id-RICcontrolHeaderVone,
	id-RICcontrolMessageVone,
	id-RICcontrolOutcomeVone,
	id-RICcontrolStatusVone,
	id-RICindicationHeaderVone,
	id-RICindicationMessageVone,
	id-RICindicationSNVone,
	id-RICindicationTypeVone,
	id-RICrequestIDVone,
	id-RICserviceQueryVone,
	id-RICsubscriptionDetailsVone,
	id-TimeToWaitVone,
	id-TNLinformationVone,
	
	maxofE2nodeComponentsVone,
	maxofRANfunctionIDVone,
	maxofRICactionIDVone,
	maxofTNLAVone
FROM E2AP-Constants;

-- **************************************************************
--
-- MESSAGES FOR NEAR-RT RIC FUNCTIONAL PROCEDURES
--
-- **************************************************************

-- **************************************************************
--
-- RIC Subscription Elementary Procedure
--
-- **************************************************************
-- **************************************************************
--
-- RIC SUBSCRIPTION REQUEST
--
-- **************************************************************
    RICsubscriptionRequestVone ::= SEQUENCE {
	protocolIEs					ProtocolIE-Container	{{RICsubscriptionRequestVone-IEs}},
	...
}

RICsubscriptionRequestVone-IEs E2AP-PROTOCOL-IES-VONE ::= {
	{ ID id-RICrequestIDVone				CRITICALITY reject	TYPE RICrequestIDVone					PRESENCE mandatory}|
	{ ID id-RANfunctionIDVone				CRITICALITY reject	TYPE RANfunctionIDVone					PRESENCE mandatory}|
	{ ID id-RICsubscriptionDetailsVone		CRITICALITY reject	TYPE RICsubscriptionDetailsVone			PRESENCE mandatory},
	...
}


RICsubscriptionDetailsVone ::= SEQUENCE {
	ricEventTriggerDefinition	RICeventTriggerDefinitionVone,
	ricAction-ToBeSetup-List	RICactions-ToBeSetup-List-Vone,
	...
}

RICactions-ToBeSetup-List-Vone ::= SEQUENCE (SIZE(1..maxofRICactionIDVone)) OF ProtocolIE-SingleContainer { {RICaction-ToBeSetup-ItemIEs-Vone} }

RICaction-ToBeSetup-ItemIEs-Vone 	E2AP-PROTOCOL-IES-VONE ::= {
	{ ID id-RICaction-ToBeSetup-Item-Vone	CRITICALITY ignore 	TYPE RICaction-ToBeSetup-Item-Vone 	PRESENCE mandatory },
	...
}

RICaction-ToBeSetup-Item-Vone ::= SEQUENCE {
	ricActionID					RICactionIDVone,
	ricActionType				RICactionTypeVone,
	ricActionDefinition			RICactionDefinitionVone 	OPTIONAL,
	ricSubsequentAction			RICsubsequentActionVone 	OPTIONAL,
	...
}

-- **************************************************************
--
-- RIC SUBSCRIPTION RESPONSE
--
-- **************************************************************
RICsubscriptionResponseVone ::= SEQUENCE {
	protocolIEs					ProtocolIE-Container{{RICsubscriptionResponseVone-IEs}},
	...
}

RICsubscriptionResponseVone-IEs E2AP-PROTOCOL-IES-VONE ::= {
	{ ID id-RICrequestIDVone				CRITICALITY reject		TYPE RICrequestIDVone				PRESENCE mandatory } |
	{ ID id-RANfunctionIDVone				CRITICALITY reject		TYPE RANfunctionIDVone				PRESENCE mandatory } |
	{ ID id-RICactions-Admitted			CRITICALITY reject		TYPE RICaction-Admitted-List-Vone	PRESENCE mandatory } |
	{ ID id-RICactions-NotAdmitted		CRITICALITY reject		TYPE RICaction-NotAdmitted-List-Vone	PRESENCE optional },
	...
}



RICaction-Admitted-List-Vone ::= SEQUENCE (SIZE(1..maxofRICactionIDVone)) OF ProtocolIE-SingleContainer{{RICaction-Admitted-ItemIEs-Vone}}

RICaction-Admitted-ItemIEs-Vone E2AP-PROTOCOL-IES-VONE ::= {
	{ ID id-RICaction-Admitted-Item-Vone		CRITICALITY ignore		TYPE RICaction-Admitted-Item-Vone	PRESENCE mandatory },
	...
}

RICaction-Admitted-Item-Vone ::= SEQUENCE {
	ricActionID					RICactionIDVone,
	...
}

RICaction-NotAdmitted-List-Vone ::= SEQUENCE (SIZE(0..maxofRICactionIDVone)) OF ProtocolIE-SingleContainer { {RICaction-NotAdmitted-ItemIEs-Vone} }

RICaction-NotAdmitted-ItemIEs-Vone E2AP-PROTOCOL-IES-VONE ::= {
	{ ID id-RICaction-NotAdmitted-Item-Vone	CRITICALITY ignore	TYPE RICaction-NotAdmitted-Item-Vone		PRESENCE mandatory },
	...
}

RICaction-NotAdmitted-Item-Vone ::= SEQUENCE {
	ricActionID					RICactionIDVone,
	cause						CauseVone,
	...
}

-- **************************************************************
--
-- RIC SUBSCRIPTION FAILURE
--
-- **************************************************************
RICsubscriptionFailureVone ::= SEQUENCE {
	protocolIEs					ProtocolIE-Container	{{RICsubscriptionFailureVone-IEs}},
	...
}

RICsubscriptionFailureVone-IEs E2AP-PROTOCOL-IES-VONE ::= {
	{ ID id-RICrequestIDVone				CRITICALITY reject	TYPE RICrequestIDVone					PRESENCE mandatory	}|
	{ ID id-RANfunctionIDVone				CRITICALITY reject	TYPE RANfunctionIDVone					PRESENCE mandatory	}|
	{ ID id-RICactions-NotAdmitted		CRITICALITY reject	TYPE RICaction-NotAdmitted-List-Vone		PRESENCE mandatory	}|
	{ ID id-CriticalityDiagnosticsVone		CRITICALITY ignore	TYPE CriticalityDiagnosticsVone			PRESENCE optional	},
	...
}

-- **************************************************************
--
-- RIC Subscription Delete Elementary Procedure
--
-- **************************************************************
-- **************************************************************
--
-- RIC SUBSCRIPTION DELETE REQUEST
--
-- **************************************************************
RICsubscriptionDeleteRequestVone ::= SEQUENCE {
	protocolIEs					ProtocolIE-Container	{{RICsubscriptionDeleteRequestVone-IEs}},
	...
}

RICsubscriptionDeleteRequestVone-IEs E2AP-PROTOCOL-IES-VONE ::= {
	{ ID id-RICrequestIDVone				CRITICALITY reject	TYPE RICrequestIDVone					PRESENCE mandatory	}|
	{ ID id-RANfunctionIDVone				CRITICALITY reject	TYPE RANfunctionIDVone					PRESENCE mandatory	},
	...
}

-- **************************************************************
--
-- RIC SUBSCRIPTION DELETE RESPONSE
--
-- **************************************************************
RICsubscriptionDeleteResponseVone ::= SEQUENCE {
	protocolIEs					ProtocolIE-Container	{{RICsubscriptionDeleteResponseVone-IEs}},
	...
}

RICsubscriptionDeleteResponseVone-IEs E2AP-PROTOCOL-IES-VONE ::= {
	{ ID id-RICrequestIDVone				CRITICALITY reject	TYPE RICrequestIDVone					PRESENCE mandatory	}|
	{ ID id-RANfunctionIDVone				CRITICALITY reject	TYPE RANfunctionIDVone					PRESENCE mandatory	},
	...
}
-- **************************************************************
--
-- RIC SUBSCRIPTION DELETE FAILURE
--
-- **************************************************************
RICsubscriptionDeleteFailureVone ::= SEQUENCE {
	protocolIEs					ProtocolIE-Container	{{RICsubscriptionDeleteFailureVone-IEs}},
	...
}

RICsubscriptionDeleteFailureVone-IEs E2AP-PROTOCOL-IES-VONE ::= {
	{ ID id-RICrequestIDVone				CRITICALITY reject	TYPE RICrequestIDVone					PRESENCE mandatory	}|
	{ ID id-RANfunctionIDVone				CRITICALITY reject	TYPE RANfunctionIDVone					PRESENCE mandatory	}|
	{ ID id-CauseVone						CRITICALITY ignore	TYPE CauseVone							PRESENCE mandatory	}|
	{ ID id-CriticalityDiagnosticsVone		CRITICALITY ignore	TYPE CriticalityDiagnosticsVone			PRESENCE optional	},
	...
}

-- **************************************************************
--
-- RIC Indication Elementary Procedure
--
-- **************************************************************
-- **************************************************************
--
-- RIC INDICATION
--
-- **************************************************************
RICindicationVone ::= SEQUENCE {
	protocolIEs					ProtocolIE-Container	{{RICindicationVone-IEs}},
	...
}

RICindicationVone-IEs E2AP-PROTOCOL-IES-VONE ::= {
	{ ID id-RICrequestIDVone				CRITICALITY reject	TYPE RICrequestIDVone					PRESENCE mandatory	}|
	{ ID id-RANfunctionIDVone				CRITICALITY reject	TYPE RANfunctionIDVone					PRESENCE mandatory	}|
	{ ID id-RICactionIDVone					CRITICALITY reject	TYPE RICactionIDVone					PRESENCE mandatory	}|
	{ ID id-RICindicationSNVone				CRITICALITY reject	TYPE RICindicationSNVone				PRESENCE optional	}|
	{ ID id-RICindicationTypeVone			CRITICALITY reject	TYPE RICindicationTypeVone  			PRESENCE mandatory	}|
	{ ID id-RICindicationHeaderVone			CRITICALITY reject	TYPE RICindicationHeaderVone			PRESENCE mandatory	}|
	{ ID id-RICindicationMessageVone		CRITICALITY reject	TYPE RICindicationMessageVone			PRESENCE mandatory	}|
	{ ID id-RICcallProcessIDVone			CRITICALITY reject	TYPE RICcallProcessIDVone				PRESENCE optional	},
	...
}

-- **************************************************************
--
-- RIC Control Elementary Procedure
--
-- **************************************************************
-- **************************************************************
--
-- RIC CONTROL REQUEST
--
-- **************************************************************
RICcontrolRequestVone ::= SEQUENCE {
	protocolIEs					ProtocolIE-Container	{{RICcontrolRequestVone-IEs}},
	...
}

RICcontrolRequestVone-IEs E2AP-PROTOCOL-IES-VONE ::= {
	{ ID id-RICrequestIDVone				CRITICALITY reject	TYPE RICrequestIDVone					PRESENCE mandatory	}|
	{ ID id-RANfunctionIDVone				CRITICALITY reject	TYPE RANfunctionIDVone					PRESENCE mandatory	}|
	{ ID id-RICcallProcessIDVone			CRITICALITY reject	TYPE RICcallProcessIDVone				PRESENCE optional	}|
	{ ID id-RICcontrolHeaderVone			CRITICALITY reject	TYPE RICcontrolHeaderVone				PRESENCE mandatory	}|
	{ ID id-RICcontrolMessageVone			CRITICALITY reject	TYPE RICcontrolMessageVone				PRESENCE mandatory	}|
	{ ID id-RICcontrolAckRequestVone		CRITICALITY reject	TYPE RICcontrolAckRequestVone			PRESENCE optional	},
	...
}
-- **************************************************************
--
-- RIC CONTROL ACKNOWLEDGE
--
-- **************************************************************
RICcontrolAcknowledgeVone ::= SEQUENCE {
	protocolIEs					ProtocolIE-Container	{{RICcontrolAcknowledgeVone-IEs}},
	...
}

RICcontrolAcknowledgeVone-IEs E2AP-PROTOCOL-IES-VONE ::= {
	{ ID id-RICrequestIDVone				CRITICALITY reject	TYPE RICrequestIDVone					PRESENCE mandatory	}|
	{ ID id-RANfunctionIDVone				CRITICALITY reject	TYPE RANfunctionIDVone					PRESENCE mandatory	}|
	{ ID id-RICcallProcessIDVone			CRITICALITY reject	TYPE RICcallProcessIDVone				PRESENCE optional	}|
	{ ID id-RICcontrolStatusVone			CRITICALITY reject	TYPE RICcontrolStatusVone				PRESENCE mandatory	} |
	{ ID id-RICcontrolOutcomeVone			CRITICALITY reject	TYPE RICcontrolOutcomeVone				PRESENCE optional	},
	...
}
-- **************************************************************
--
-- RIC CONTROL FAILURE
--
-- **************************************************************
RICcontrolFailureVone ::= SEQUENCE {
	protocolIEs					ProtocolIE-Container	{{RICcontrolFailureVone-IEs}},
	...
}

RICcontrolFailureVone-IEs E2AP-PROTOCOL-IES-VONE ::= {
	{ ID id-RICrequestIDVone				CRITICALITY reject	TYPE RICrequestIDVone					PRESENCE mandatory	}|
	{ ID id-RANfunctionIDVone				CRITICALITY reject	TYPE RANfunctionIDVone					PRESENCE mandatory	}|
	{ ID id-RICcallProcessIDVone			CRITICALITY reject	TYPE RICcallProcessIDVone				PRESENCE optional	}|
	{ ID id-CauseVone						CRITICALITY ignore	TYPE CauseVone							PRESENCE mandatory	} |
	{ ID id-RICcontrolOutcomeVone			CRITICALITY reject	TYPE RICcontrolOutcomeVone				PRESENCE optional	},
	...
}

-- **************************************************************
--
-- MESSAGES FOR GLOBAL PROCEDURES
--
-- **************************************************************

-- **************************************************************
--
-- Error Indication Elementary Procedure
--
-- **************************************************************
-- **************************************************************
--
-- ERROR INDICATION
--
-- **************************************************************
ErrorIndicationVone ::= SEQUENCE {
	protocolIEs					ProtocolIE-Container	{{ErrorIndicationVone-IEs}},
	...
}

ErrorIndicationVone-IEs E2AP-PROTOCOL-IES-VONE ::= {
	{ ID id-RICrequestIDVone				CRITICALITY reject	TYPE RICrequestIDVone				PRESENCE optional	}|
	{ ID id-RANfunctionIDVone				CRITICALITY reject	TYPE RANfunctionIDVone				PRESENCE optional	}|
	{ ID id-CauseVone						CRITICALITY ignore	TYPE CauseVone						PRESENCE optional	}|
	{ ID id-CriticalityDiagnosticsVone		CRITICALITY ignore	TYPE CriticalityDiagnosticsVone		PRESENCE optional	},
	...
}

-- **************************************************************
--
-- E2 Setup Elementary Procedure
--
-- **************************************************************
-- **************************************************************
--
-- E2 SETUP REQUEST
--
-- **************************************************************

E2setupRequestVone ::= SEQUENCE {
	protocolIEs		ProtocolIE-Container		{ {E2setupRequestIEsVone} },
	...
}

E2setupRequestIEsVone E2AP-PROTOCOL-IES-VONE ::= {
	{ ID id-GlobalE2node-IDVone				CRITICALITY reject	TYPE GlobalE2node-IDVone				PRESENCE mandatory	}|
	{ ID id-RANfunctionsAdded			CRITICALITY reject	TYPE RANfunctions-List-Vone				PRESENCE optional	}|
	{ ID id-E2nodeComponentConfigUpdateVone	CRITICALITY reject	TYPE E2nodeComponentConfigUpdateVone-List	PRESENCE optional	},
	...
}

-- **************************************************************
--
-- E2 SETUP RESPONSE
--
-- **************************************************************

E2setupResponseVone ::= SEQUENCE {
	protocolIEs		ProtocolIE-Container		{ {E2setupResponseIEsVone} },
	...
}

E2setupResponseIEsVone E2AP-PROTOCOL-IES-VONE ::= {
	{ ID id-GlobalRIC-IDVone					CRITICALITY reject	TYPE GlobalRIC-IDVone							PRESENCE mandatory	}|
	{ ID id-RANfunctionsAccepted			CRITICALITY reject	TYPE RANfunctionsID-List-Vone					PRESENCE optional	}|
	{ ID id-RANfunctionsRejected			CRITICALITY reject	TYPE RANfunctionsIDcause-List-Vone				PRESENCE optional	}|
	{ ID id-E2nodeComponentConfigUpdateAckVone	CRITICALITY reject	TYPE E2nodeComponentConfigUpdateAckVone-List	PRESENCE optional	},
	...
}

-- **************************************************************
--
-- E2 SETUP FAILURE
--
-- **************************************************************

E2setupFailureVone ::= SEQUENCE {
	protocolIEs		ProtocolIE-Container		{ {E2setupFailureIEsVone} },
	...
}

E2setupFailureIEsVone E2AP-PROTOCOL-IES-VONE ::= {
	{ ID id-CauseVone						CRITICALITY ignore	TYPE CauseVone						PRESENCE mandatory	}|
	{ ID id-TimeToWaitVone					CRITICALITY ignore	TYPE TimeToWaitVone					PRESENCE optional	}|
	{ ID id-CriticalityDiagnosticsVone		CRITICALITY ignore	TYPE CriticalityDiagnosticsVone		PRESENCE optional	}|
	{ ID id-TNLinformationVone				CRITICALITY ignore	TYPE TNLinformationVone		PRESENCE optional	},
	...
}

-- **************************************************************
--
-- E2 Connection Update Elementary Procedure
--
-- **************************************************************
-- **************************************************************
--
-- E2 CONNECTION UPDATE
--
-- **************************************************************
E2connectionUpdateVone ::= SEQUENCE {
	protocolIEs					ProtocolIE-Container	{{E2connectionUpdateVone-IEs}},
	...
}

E2connectionUpdateVone-IEs E2AP-PROTOCOL-IES-VONE ::= {
	{ ID id-E2connectionUpdateAdd		CRITICALITY reject	TYPE E2connectionUpdateVone-List			PRESENCE optional	}|
	{ ID id-E2connectionUpdateRemove	CRITICALITY reject	TYPE E2connectionUpdateRemoveVone-List		PRESENCE optional	}|
	{ ID id-E2connectionUpdateModify	CRITICALITY reject	TYPE E2connectionUpdateVone-List			PRESENCE optional	},
	...
}

E2connectionUpdateVone-List ::= SEQUENCE (SIZE(1..maxofTNLAVone)) OF ProtocolIE-SingleContainer { {E2connectionUpdateVone-ItemIEs} }

E2connectionUpdateVone-ItemIEs 	E2AP-PROTOCOL-IES-VONE ::= {
	{ ID id-E2connectionUpdateVone-Item			CRITICALITY ignore 	TYPE E2connectionUpdateVone-Item 		PRESENCE mandatory	},
	...
}

E2connectionUpdateVone-Item ::= SEQUENCE {
	tnlInformation					TNLinformationVone,
	tnlUsage  						TNLusageVone,
	...
}

E2connectionUpdateRemoveVone-List ::= SEQUENCE (SIZE(1..maxofTNLAVone)) OF ProtocolIE-SingleContainer { {E2connectionUpdateRemove-ItemIEs-Vone} }

E2connectionUpdateRemove-ItemIEs-Vone 	E2AP-PROTOCOL-IES-VONE ::= {
	{ ID id-E2connectionUpdateRemove-Item-Vone	CRITICALITY ignore 	TYPE E2connectionUpdateRemove-Item-Vone 	PRESENCE mandatory	},
	...
}

E2connectionUpdateRemove-Item-Vone ::= SEQUENCE {
	tnlInformation					TNLinformationVone,
	...
}



-- **************************************************************
--
-- E2 CONNECTION UPDATE ACKNOWLEDGE
--
-- **************************************************************
E2connectionUpdateAcknowledgeVone ::= SEQUENCE {
	protocolIEs					ProtocolIE-Container	{{E2connectionUpdateAck-IEs-Vone}},
	...
}

E2connectionUpdateAck-IEs-Vone E2AP-PROTOCOL-IES-VONE ::= {
	{ ID id-E2connectionSetup			CRITICALITY reject	TYPE E2connectionUpdateVone-List			PRESENCE optional	}|
	{ ID id-E2connectionSetupFailed		CRITICALITY reject	TYPE E2connectionSetupFailedVone-List		PRESENCE optional	},
	...
}

E2connectionSetupFailedVone-List ::= SEQUENCE (SIZE(1..maxofTNLAVone)) OF ProtocolIE-SingleContainer { {E2connectionSetupFailed-ItemIEs-Vone} }

E2connectionSetupFailed-ItemIEs-Vone 	E2AP-PROTOCOL-IES-VONE ::= {
	{ ID id-E2connectionSetupFailed-Item-Vone			CRITICALITY ignore 	TYPE E2connectionSetupFailed-Item-Vone 		PRESENCE mandatory	},
	...
}

E2connectionSetupFailed-Item-Vone ::= SEQUENCE {
	tnlInformation					TNLinformationVone,
	cause							CauseVone,
	...
}

-- **************************************************************
--
-- E2 CONNECTION UPDATE FAILURE
--
-- **************************************************************
E2connectionUpdateFailureVone ::= SEQUENCE {
	protocolIEs			ProtocolIE-Container	{{E2connectionUpdateFailureVone-IEs}},
	...
}

E2connectionUpdateFailureVone-IEs E2AP-PROTOCOL-IES-VONE ::= {
	{ ID id-CauseVone								CRITICALITY reject	TYPE CauseVone									PRESENCE optional	}|
	{ ID id-TimeToWaitVone							CRITICALITY ignore	TYPE TimeToWaitVone								PRESENCE optional	}|
	{ ID id-CriticalityDiagnosticsVone				CRITICALITY ignore	TYPE CriticalityDiagnosticsVone					PRESENCE optional	},
	...
}

-- **************************************************************
--
-- E2 Node Configuration Update Elementary Procedure
--
-- **************************************************************
-- **************************************************************
--
-- E2 NODE CONFIGURATION UPDATE
--
-- **************************************************************
E2nodeConfigurationUpdateVone ::= SEQUENCE {
	protocolIEs					ProtocolIE-Container	{{E2nodeConfigurationUpdateVone-IEs}},
	...
}

E2nodeConfigurationUpdateVone-IEs E2AP-PROTOCOL-IES-VONE ::= {
	{ ID id-E2nodeComponentConfigUpdateVone		CRITICALITY reject	TYPE E2nodeComponentConfigUpdateVone-List			PRESENCE optional	},
	...
}

E2nodeComponentConfigUpdateVone-List ::= SEQUENCE (SIZE(1..maxofE2nodeComponentsVone)) OF ProtocolIE-SingleContainer { {E2nodeComponentConfigUpdateVone-ItemIEs} }

E2nodeComponentConfigUpdateVone-ItemIEs 	E2AP-PROTOCOL-IES-VONE ::= {
	{ ID id-E2nodeComponentConfigUpdateVone-Item			CRITICALITY reject 	TYPE E2nodeComponentConfigUpdateVone-Item 				PRESENCE mandatory	},
	...
}


E2nodeComponentConfigUpdateVone-Item ::= SEQUENCE {
	e2nodeComponentType					E2nodeComponentTypeVone,
	e2nodeComponentID					E2nodeComponentIDVone			OPTIONAL,
	e2nodeComponentConfigUpdate  		E2nodeComponentConfigUpdateVone,
	...
}


-- **************************************************************
--
-- E2 NODE CONFIGURATION UPDATE ACKNOWLEDGE
--
-- **************************************************************
E2nodeConfigurationUpdateAcknowledgeVone ::= SEQUENCE {
	protocolIEs					ProtocolIE-Container	{{E2nodeConfigurationUpdateAcknowledgeVone-IEs}},
	...
}

E2nodeConfigurationUpdateAcknowledgeVone-IEs E2AP-PROTOCOL-IES-VONE ::= {
	{ ID id-E2nodeComponentConfigUpdateAckVone			CRITICALITY reject	TYPE E2nodeComponentConfigUpdateAckVone-List		PRESENCE optional	},
	...
}

E2nodeComponentConfigUpdateAckVone-List ::= SEQUENCE (SIZE(1..maxofE2nodeComponentsVone)) OF ProtocolIE-SingleContainer { {E2nodeComponentConfigUpdateAckVone-ItemIEs} }

E2nodeComponentConfigUpdateAckVone-ItemIEs 	E2AP-PROTOCOL-IES-VONE ::= {
	{ ID id-E2nodeComponentConfigUpdateAckVone-Item			CRITICALITY reject 	TYPE E2nodeComponentConfigUpdateAckVone-Item 	PRESENCE mandatory	},
	...
}


E2nodeComponentConfigUpdateAckVone-Item ::= SEQUENCE {
	e2nodeComponentType					E2nodeComponentTypeVone,
	e2nodeComponentID					E2nodeComponentIDVone			OPTIONAL,
	e2nodeComponentConfigUpdateAck	E2nodeComponentConfigUpdateAckVone,
	...
}


-- **************************************************************
--
-- E2 NODE CONFIGURATION UPDATE FAILURE
--
-- **************************************************************
E2nodeConfigurationUpdateFailureVone ::= SEQUENCE {
	protocolIEs			ProtocolIE-Container	{{E2nodeConfigurationUpdateFailureVone-IEs}},
	...
}

E2nodeConfigurationUpdateFailureVone-IEs E2AP-PROTOCOL-IES-VONE ::= {
	{ ID id-CauseVone								CRITICALITY ignore	TYPE CauseVone										PRESENCE mandatory	}|
	{ ID id-TimeToWaitVone							CRITICALITY ignore	TYPE TimeToWaitVone									PRESENCE optional	}|
	{ ID id-CriticalityDiagnosticsVone				CRITICALITY ignore	TYPE CriticalityDiagnosticsVone						PRESENCE optional	},
	...
}

-- **************************************************************
--
-- Reset Elementary Procedure
--
-- **************************************************************

-- **************************************************************
--
-- RESET REQUEST
--
-- **************************************************************

ResetRequestVone ::= SEQUENCE {
	protocolIEs		ProtocolIE-Container		{ {ResetRequestIEsVone} },
	...
}

ResetRequestIEsVone E2AP-PROTOCOL-IES-VONE ::= {
	{ ID id-CauseVone						CRITICALITY ignore	TYPE CauseVone						PRESENCE mandatory	},
	...
}

-- **************************************************************
--
-- RESET RESPONSE
--
-- **************************************************************

ResetResponseVone ::= SEQUENCE {
	protocolIEs		ProtocolIE-Container		{ {ResetResponseIEsVone} },
	...
}

ResetResponseIEsVone E2AP-PROTOCOL-IES-VONE ::= {
	{ ID id-CriticalityDiagnosticsVone		CRITICALITY ignore	TYPE CriticalityDiagnosticsVone		PRESENCE optional	},
	...
}

-- **************************************************************
--
-- RIC Service Update Elementary Procedure
--
-- **************************************************************
-- **************************************************************
--
-- RIC SERVICE UPDATE
--
-- **************************************************************
RICserviceUpdateVone ::= SEQUENCE {
	protocolIEs					ProtocolIE-Container	{{RICserviceUpdateVone-IEs}},
	...
}

RICserviceUpdateVone-IEs E2AP-PROTOCOL-IES-VONE ::= {
	{ ID id-RANfunctionsAdded			CRITICALITY reject	TYPE RANfunctions-List-Vone				PRESENCE optional	}|
	{ ID id-RANfunctionsModified		CRITICALITY reject	TYPE RANfunctions-List-Vone				PRESENCE optional	}|
	{ ID id-RANfunctionsDeleted			CRITICALITY reject	TYPE RANfunctionsID-List-Vone			PRESENCE optional	},
	...
}

RANfunctions-List-Vone ::= SEQUENCE (SIZE(0..maxofRANfunctionIDVone)) OF ProtocolIE-SingleContainer { {RANfunction-ItemIEs-Vone} }

RANfunction-ItemIEs-Vone 	E2AP-PROTOCOL-IES-VONE ::= {
	{ ID id-RANfunction-Item-Vone			CRITICALITY ignore 	TYPE RANfunction-Item-Vone 				PRESENCE mandatory	},
	...
}


RANfunction-Item-Vone ::= SEQUENCE {
	ranFunctionID				RANfunctionIDVone,
	ranFunctionDefinition  		RANfunctionDefinitionVone,
	ranFunctionRevision			RANfunctionRevisionVone,
	...,
	ranFunctionOID				RANfunctionOIDVone		OPTIONAL
}

RANfunctionsID-List-Vone ::= SEQUENCE (SIZE(0..maxofRANfunctionIDVone)) OF ProtocolIE-SingleContainer{{RANfunctionIDVone-ItemIEs}}

RANfunctionIDVone-ItemIEs E2AP-PROTOCOL-IES-VONE ::= {
	{ ID id-RANfunctionIDVone-Item			CRITICALITY ignore		TYPE RANfunctionIDVone-Item			PRESENCE mandatory	},
	...
}

RANfunctionIDVone-Item ::= SEQUENCE {
	ranFunctionID				RANfunctionIDVone,
	ranFunctionRevision			RANfunctionRevisionVone,
	...
}

-- **************************************************************
--
-- RIC SERVICE UPDATE ACKNOWLEDGE
--
-- **************************************************************
RICserviceUpdateAcknowledgeVone ::= SEQUENCE {
	protocolIEs					ProtocolIE-Container	{{RICserviceUpdateAcknowledgeVone-IEs}},
	...
}

RICserviceUpdateAcknowledgeVone-IEs E2AP-PROTOCOL-IES-VONE ::= {
	{ ID id-RANfunctionsAccepted		CRITICALITY reject	TYPE RANfunctionsID-List-Vone			PRESENCE optional	}|
	{ ID id-RANfunctionsRejected		CRITICALITY reject	TYPE RANfunctionsIDcause-List-Vone		PRESENCE optional	},
	...
}

RANfunctionsIDcause-List-Vone ::= SEQUENCE (SIZE(0..maxofRANfunctionIDVone)) OF ProtocolIE-SingleContainer { {RANfunctionIDcause-ItemIEs-Vone} }

RANfunctionIDcause-ItemIEs-Vone 	E2AP-PROTOCOL-IES-VONE ::= {
	{ ID id-RANfunctionIEcause-Item		CRITICALITY ignore 	TYPE RANfunctionIDcause-Item-Vone 		PRESENCE mandatory	},
	...
}


RANfunctionIDcause-Item-Vone ::= SEQUENCE {
	ranFunctionID				RANfunctionIDVone,
	cause						CauseVone,
	...
}


-- **************************************************************
--
-- RIC SERVICE UPDATE FAILURE
--
-- **************************************************************
RICserviceUpdateFailureVone ::= SEQUENCE {
	protocolIEs			ProtocolIE-Container	{{RICserviceUpdateFailureVone-IEs}},
	...
}

RICserviceUpdateFailureVone-IEs E2AP-PROTOCOL-IES-VONE ::= {
	{ ID id-RANfunctionsRejected		CRITICALITY ignore	TYPE RANfunctionsIDcause-List-Vone		PRESENCE optional	}|
	{ ID id-TimeToWaitVone					CRITICALITY ignore	TYPE TimeToWaitVone						PRESENCE optional	}|
	{ ID id-CriticalityDiagnosticsVone		CRITICALITY ignore	TYPE CriticalityDiagnosticsVone			PRESENCE optional	},
	...
}

-- **************************************************************
--
-- RIC Service Query Elementary Procedure
--
-- **************************************************************
-- **************************************************************
--
-- RIC SERVICE QUERY
--
-- **************************************************************
RICserviceQueryVone ::= SEQUENCE {
	protocolIEs					ProtocolIE-Container	{{RICserviceQueryVone-IEs}},
	...
}

RICserviceQueryVone-IEs E2AP-PROTOCOL-IES-VONE ::= {
	{ ID id-RANfunctionsAccepted		CRITICALITY reject	TYPE RANfunctionsID-List-Vone			PRESENCE optional	},
	...
}

END
-- **************************************************************
-- E2AP
-- Information Element Definitions
--
-- **************************************************************

E2AP-IEs {
iso(1) identified-organization(3) dod(6) internet(1) private(4) enterprise(1) 53148 e2(1) version1 (1) e2ap(1) e2ap-IEs (2)}

DEFINITIONS AUTOMATIC TAGS ::=

BEGIN

IMPORTS
	CriticalityVone,
	PresenceVone,
	ProcedureCodeVone,
	ProtocolIE-ID-Vone,
	TriggeringMessageVone
FROM E2AP-CommonDataTypes

	maxnoofErrorsVone,
	maxProtocolIEsVone
FROM E2AP-Constants;

-- A
-- B
-- C
CauseVone ::= CHOICE {
	ricRequest			CauseRICVone,
	ricService			CauseRICserviceVone,
	transport			CauseTransportVone,
	protocol			CauseProtocolVone,
	misc				CauseMiscVone,
	...
}

CauseMiscVone ::= ENUMERATED {
	control-processing-overload,
	hardware-failure,
	om-intervention,
	unspecified,
	...
}
CauseProtocolVone ::= ENUMERATED {
	transfer-syntax-error,
	abstract-syntax-error-reject,
	abstract-syntax-error-ignore-and-notify,
	message-not-compatible-with-receiver-state,
	semantic-error,
	abstract-syntax-error-falsely-constructed-message,
	unspecified,
	...
}

CauseRICVone ::= ENUMERATED {
	ran-function-id-Invalid,
	action-not-supported,
	excessive-actions,
	duplicate-action,
	duplicate-event,
	function-resource-limit,
	request-id-unknown,
	inconsistent-action-subsequent-action-sequence,
	control-message-invalid,
	call-process-id-invalid,
	unspecified,
	...
}

CauseRICserviceVone ::= ENUMERATED{
	function-not-required,
	excessive-functions,
	ric-resource-limit,
	...
}
CauseTransportVone ::= ENUMERATED {
	unspecified,
	transport-resource-unavailable,
	...
}

-- **************************************************************
-- copied from 3GPP 38.413 NGAP IEs v15.5.0
-- note: ie-Extensions removed
-- **************************************************************
CriticalityDiagnosticsVone ::= SEQUENCE {
	procedureCode					ProcedureCodeVone							OPTIONAL,
	triggeringMessage				TriggeringMessageVone						OPTIONAL,
	procedureCriticality			CriticalityVone								OPTIONAL,
	ricRequestorID					RICrequestIDVone							OPTIONAL,
	iEsCriticalityDiagnostics		CriticalityDiagnosticsVone-IE-List			OPTIONAL,
	...
}

CriticalityDiagnosticsVone-IE-List ::= SEQUENCE (SIZE(1..maxnoofErrorsVone)) OF CriticalityDiagnosticsVone-IE-Item

CriticalityDiagnosticsVone-IE-Item ::= SEQUENCE {
	iECriticality		CriticalityVone,
	iE-ID				ProtocolIE-ID-Vone,
	typeOfError			TypeOfErrorVone,
	...
}

-- D
-- E

-- Following IE used to carry 3GPP defined RAN Configuration Update message defined in F1AP, E1AP, XnAP, etc.
E2nodeComponentConfigUpdateVone ::= CHOICE{
	gNBconfigUpdate		E2nodeComponentConfigUpdateGNBVone,
	en-gNBconfigUpdate	E2nodeComponentConfigUpdateENgNBVone,
	ng-eNBconfigUpdate	E2nodeComponentConfigUpdateNGeNBVone,
	eNBconfigUpdate		E2nodeComponentConfigUpdateENBVone,
	...
}

E2nodeComponentConfigUpdateGNBVone ::= SEQUENCE{
	ngAPconfigUpdate	OCTET STRING	OPTIONAL,
	xnAPconfigUpdate	OCTET STRING	OPTIONAL,
	e1APconfigUpdate	OCTET STRING	OPTIONAL,
	f1APconfigUpdate	OCTET STRING	OPTIONAL,
	...
}

E2nodeComponentConfigUpdateENgNBVone ::= SEQUENCE{
	x2APconfigUpdate	OCTET STRING	OPTIONAL,
	...
}

E2nodeComponentConfigUpdateNGeNBVone ::= SEQUENCE{
	ngAPconfigUpdate	OCTET STRING	OPTIONAL,
	xnAPconfigUpdate	OCTET STRING	OPTIONAL,
	...
}

E2nodeComponentConfigUpdateENBVone ::= SEQUENCE{
	s1APconfigUpdate	OCTET STRING	OPTIONAL,
	x2APconfigUpdate	OCTET STRING	OPTIONAL,
	...
}

E2nodeComponentConfigUpdateAckVone ::= SEQUENCE{
	updateOutcome		ENUMERATED {success, failure, ...},
	failureCause		CauseVone			OPTIONAL,
	...
}

E2nodeComponentTypeVone ::= ENUMERATED {gNB, gNB-CU-UP, gNB-DU, en-gNB, eNB, ng-eNB, ...}

E2nodeComponentIDVone ::= CHOICE{
	e2nodeComponentTypeGNB-CU-UP	E2nodeComponentGNB-CU-UP-ID-Vone,
	e2nodeComponentTypeGNB-DU		E2nodeComponentGNB-DU-ID-Vone,
	...
}

E2nodeComponentGNB-CU-UP-ID-Vone ::= SEQUENCE{
	gNB-CU-UP-ID		GNB-CU-UP-ID-Vone,
	...
}

E2nodeComponentGNB-DU-ID-Vone ::= SEQUENCE{
	gNB-DU-ID			GNB-DU-ID-Vone,
	...
}

-- **************************************************************
-- copied from 3GPP X2AP IEs v15.4.0
-- note: ie-Extensions removed
-- **************************************************************
ENB-ID-Vone ::= CHOICE {
	macro-eNB-ID			BIT STRING (SIZE (20)),
	home-eNB-ID				BIT STRING (SIZE (28)),
	... ,
	short-Macro-eNB-ID		BIT STRING (SIZE(18)),
	long-Macro-eNB-ID		BIT STRING (SIZE(21))
}
-- **************************************************************
-- copied from 3GPP 38.423 v15.5.0 XnAP IEs
-- **************************************************************
ENB-ID-Vone-Choice ::= CHOICE {
	enb-ID-macro			BIT STRING (SIZE(20)),
	enb-ID-shortmacro		BIT STRING (SIZE(18)),
	enb-ID-longmacro		BIT STRING (SIZE(21)),
	...
}

-- **************************************************************
-- copied from 3GPP X2AP IEs v15.4.0
-- note: ie-Extensions removed
-- Note: to avoid duplicate names with XnAP, GNB-ID renamed ENGNB-ID-Vone, GlobalGNB-ID renamed GlobalenGNB-ID-Vone
-- **************************************************************
ENGNB-ID-Vone ::= CHOICE {
	gNB-ID	BIT STRING (SIZE (22..32)),
	...
}

-- F
-- G
GlobalE2node-IDVone ::= CHOICE{
	gNB					GlobalE2node-gNB-ID-Vone,
	en-gNB				GlobalE2node-en-gNB-ID-Vone,
	ng-eNB				GlobalE2node-ng-eNB-ID-Vone,
	eNB					GlobalE2node-eNB-ID-Vone,
	...
}

GlobalE2node-en-gNB-ID-Vone ::= SEQUENCE{
	global-gNB-ID		GlobalenGNB-ID-Vone,
	...
}
GlobalE2node-eNB-ID-Vone ::= SEQUENCE{
	global-eNB-ID		GlobalENB-ID-Vone,
	...
}
GlobalE2node-gNB-ID-Vone ::= SEQUENCE{
	global-gNB-ID		GlobalgNB-ID-Vone,
	gNB-CU-UP-ID		GNB-CU-UP-ID-Vone	OPTIONAL,
	gNB-DU-ID			GNB-DU-ID-Vone		OPTIONAL,
	...
}
GlobalE2node-ng-eNB-ID-Vone ::= SEQUENCE{
	global-ng-eNB-ID	GlobalngeNB-ID-Vone,
	...
}
-- **************************************************************
-- copied from 3GPP X2AP IEs v15.4.0
-- note: ie-Extensions removed
-- **************************************************************

GlobalENB-ID-Vone ::= SEQUENCE {
	pLMN-Identity		PLMN-Identity-Vone,
	eNB-ID				ENB-ID-Vone,
	...
}
-- **************************************************************
-- copied from 3GPP X2AP IEs v15.4.0
-- Note: to avoid duplicate names with XnAP, GNB-ID renamed ENGNB-ID-Vone, GlobalGNB-ID renamed GlobalenGNB-ID-Vone
-- **************************************************************
GlobalenGNB-ID-Vone ::= SEQUENCE {
	pLMN-Identity		PLMN-Identity-Vone,
	gNB-ID				ENGNB-ID-Vone,
	...
}
-- **************************************************************
-- copied from 3GPP 38.423 v15.5.0 XnAP IEs
-- **************************************************************
GlobalgNB-ID-Vone	::= SEQUENCE {
	plmn-id				PLMN-Identity-Vone,
	gnb-id				GNB-ID-Choice-Vone,
	...
}


-- **************************************************************
-- copied from 3GPP 38.423 v15.5.0 XnAP IEs
-- **************************************************************
GlobalngeNB-ID-Vone	::= SEQUENCE {
	plmn-id			PLMN-Identity-Vone,
	enb-id			ENB-ID-Vone-Choice,
	...
}

GlobalRIC-IDVone ::= SEQUENCE{
	pLMN-Identity			PLMN-Identity-Vone,
	ric-ID					BIT STRING (SIZE (20)),
	...
}

-- **************************************************************
-- copied from 3GPP 38.463 v15.5.0 E1AP IEs
-- **************************************************************
GNB-CU-UP-ID-Vone::= 	INTEGER (0..68719476735)
GNB-DU-ID-Vone::= 		INTEGER (0..68719476735)

-- **************************************************************
-- copied from 3GPP 38.423 v15.5.0 XnAP IEs
-- **************************************************************
GNB-ID-Choice-Vone ::= CHOICE {
	gnb-ID					BIT STRING (SIZE(22..32)),
	...
}
-- H
-- I
-- J
-- K
-- L
-- M
-- N
-- O
-- P
-- **************************************************************
-- copied from 3GPP X2AP IEs v15.4.0
-- **************************************************************
PLMN-Identity-Vone ::= OCTET STRING (SIZE(3))

-- Q
-- R
-- **************************************************************
-- Following IE defined in E2SM
-- **************************************************************
RANfunctionDefinitionVone ::= OCTET STRING

RANfunctionIDVone ::= INTEGER (0..4095)

RANfunctionOIDVone ::= PrintableString(SIZE(1..1000,...))

RANfunctionRevisionVone ::= INTEGER (0..4095)

-- **************************************************************
-- Following IE defined in E2SM
-- **************************************************************
RICactionDefinitionVone ::= OCTET STRING

RICactionIDVone ::= INTEGER (0..255)

RICactionTypeVone ::= ENUMERATED{
	report,
	insert,
	policy,
	...
}

-- **************************************************************
-- Following IE defined in E2SM
-- **************************************************************
RICcallProcessIDVone ::= OCTET STRING

RICcontrolAckRequestVone ::= ENUMERATED{
	noAck,
	ack,
	nAck,
	...
}

-- **************************************************************
-- Following IE defined in E2SM
-- **************************************************************
RICcontrolHeaderVone ::= OCTET STRING

-- **************************************************************
-- Following IE defined in E2SM
-- **************************************************************
RICcontrolMessageVone ::= OCTET STRING

-- **************************************************************
-- Following IE defined in E2SM
-- **************************************************************
RICcontrolOutcomeVone ::= OCTET STRING

RICcontrolStatusVone ::= ENUMERATED{
	success,
	rejected,
	failed,
	...
}

-- **************************************************************
-- Following IE defined in E2SM
-- **************************************************************
RICeventTriggerDefinitionVone ::= OCTET STRING

-- **************************************************************
-- Following IE defined in E2SM
-- **************************************************************
RICindicationHeaderVone ::= OCTET STRING

-- **************************************************************
-- Following IE defined in E2SM
-- **************************************************************
RICindicationMessageVone ::= OCTET STRING

RICindicationSNVone ::= INTEGER (0..65535)

RICindicationTypeVone ::= ENUMERATED{
	report,
	insert,
	...
}

RICrequestIDVone ::= SEQUENCE {
	ricRequestorID				INTEGER (0..65535),
	ricInstanceID	INTEGER (0..65535),
	...
}

RICsubsequentActionVone ::=SEQUENCE{
	ricSubsequentActionType		RICsubsequentActionTypeVone,
	ricTimeToWait				RICtimeToWaitVone,
	...
}

RICsubsequentActionTypeVone ::= ENUMERATED{
	continue,
	wait,
	...
}

RICtimeToWaitVone ::= ENUMERATED{
	zero,
	w1ms,
	w2ms,
	w5ms,
	w10ms,
	w20ms,
	w30ms,
	w40ms,
	w50ms,
	w100ms,
	w200ms,
	w500ms,
	w1s,
	w2s,
	w5s,
	w10s,
	w20s,
	w60s,
	...
}
-- S
-- T
-- **************************************************************
-- copied from 3GPP 38.413 NGAP IEs v15.5.0
-- **************************************************************
TimeToWaitVone ::= ENUMERATED {v1s, v2s, v5s, v10s, v20s, v60s, ...}


TNLinformationVone ::= SEQUENCE{
	tnlAddress			BIT STRING (SIZE(1..160,...)),
	tnlPort				BIT STRING (SIZE(16))	OPTIONAL,
	...
}

TNLusageVone ::= ENUMERATED{ric-service, support-function, both, ...}


-- **************************************************************
-- copied from 3GPP 38.413 NGAP IEs v15.5.0
-- **************************************************************
TypeOfErrorVone ::= ENUMERATED {
	not-understood,
	missing,
	...
}

-- U
-- V
-- W
-- X
-- Y
-- Z

END
-- **************************************************************
--
-- Common definitions
-- Derived from 3GPP 38.413 v15.4.0
--
-- **************************************************************

E2AP-CommonDataTypes {
iso(1) identified-organization(3) dod(6) internet(1) private(4) enterprise(1) 53148 e2(1) version1 (1) e2ap(1) e2ap-CommonDataTypes (3) }

DEFINITIONS AUTOMATIC TAGS ::=

BEGIN

CriticalityVone		::= ENUMERATED { reject, ignore, notify }

PresenceVone		::= ENUMERATED { optional, conditional, mandatory }

ProcedureCodeVone		::= INTEGER (0..255)

ProtocolIE-ID-Vone		::= INTEGER (0..65535)

TriggeringMessageVone	::= ENUMERATED { initiating-message, successful-outcome, unsuccessfull-outcome }

END
-- **************************************************************
--
-- Constant definitions
--
-- **************************************************************

E2AP-Constants {
iso(1) identified-organization(3) dod(6) internet(1) private(4) enterprise(1) 53148 e2(1) version1 (1) e2ap(1) e2ap-Constants (4) }

DEFINITIONS AUTOMATIC TAGS ::=

BEGIN

IMPORTS
	ProcedureCodeVone,
	ProtocolIE-ID-Vone
FROM E2AP-CommonDataTypes;

-- **************************************************************
--
-- Elementary Procedures
--
-- **************************************************************
id-E2setupVone									ProcedureCodeVone ::= 1
id-ErrorIndicationVone							ProcedureCodeVone ::= 2
id-ResetVone									ProcedureCodeVone ::= 3
id-RICcontrolVone								ProcedureCodeVone ::= 4
id-RICindicationVone							ProcedureCodeVone ::= 5
id-RICserviceQueryVone							ProcedureCodeVone ::= 6
id-RICserviceUpdateVone							ProcedureCodeVone ::= 7
id-RICsubscriptionVone							ProcedureCodeVone ::= 8
id-RICsubscriptionDeleteVone					ProcedureCodeVone ::= 9
id-E2nodeConfigurationUpdateVone				ProcedureCodeVone ::= 10
id-E2connectionUpdateVone						ProcedureCodeVone ::= 11

-- **************************************************************
--
-- Extension constants
--
-- **************************************************************

maxProtocolIEsVone								INTEGER ::= 65535


-- **************************************************************
--
-- Lists
--
-- **************************************************************
maxnoofErrorsVone								INTEGER ::= 256
maxofE2nodeComponentsVone						INTEGER ::= 1024
maxofRANfunctionIDVone							INTEGER ::= 256
maxofRICactionIDVone							INTEGER ::= 16
maxofTNLAVone									INTEGER ::= 32

-- **************************************************************
--
-- IEs
--
-- **************************************************************
id-CauseVone									ProtocolIE-ID-Vone ::= 1
id-CriticalityDiagnosticsVone					ProtocolIE-ID-Vone ::= 2
id-GlobalE2node-IDVone							ProtocolIE-ID-Vone ::= 3
id-GlobalRIC-IDVone								ProtocolIE-ID-Vone ::= 4
id-RANfunctionIDVone   							ProtocolIE-ID-Vone ::= 5
id-RANfunctionIDVone-Item   					ProtocolIE-ID-Vone ::= 6
id-RANfunctionIEcause-Item					ProtocolIE-ID-Vone ::= 7
id-RANfunction-Item-Vone							ProtocolIE-ID-Vone ::= 8
id-RANfunctionsAccepted						ProtocolIE-ID-Vone ::= 9
id-RANfunctionsAdded						ProtocolIE-ID-Vone ::= 10
id-RANfunctionsDeleted						ProtocolIE-ID-Vone ::= 11
id-RANfunctionsModified						ProtocolIE-ID-Vone ::= 12
id-RANfunctionsRejected						ProtocolIE-ID-Vone ::= 13
id-RICaction-Admitted-Item-Vone					ProtocolIE-ID-Vone ::= 14
id-RICactionIDVone								ProtocolIE-ID-Vone ::= 15
id-RICaction-NotAdmitted-Item-Vone				ProtocolIE-ID-Vone ::= 16
id-RICactions-Admitted						ProtocolIE-ID-Vone ::= 17
id-RICactions-NotAdmitted					ProtocolIE-ID-Vone ::= 18
id-RICaction-ToBeSetup-Item-Vone					ProtocolIE-ID-Vone ::= 19
id-RICcallProcessIDVone							ProtocolIE-ID-Vone ::= 20
id-RICcontrolAckRequestVone						ProtocolIE-ID-Vone ::= 21
id-RICcontrolHeaderVone							ProtocolIE-ID-Vone ::= 22
id-RICcontrolMessageVone						ProtocolIE-ID-Vone ::= 23
id-RICcontrolStatusVone							ProtocolIE-ID-Vone ::= 24
id-RICindicationHeaderVone						ProtocolIE-ID-Vone ::= 25
id-RICindicationMessageVone						ProtocolIE-ID-Vone ::= 26
id-RICindicationSNVone							ProtocolIE-ID-Vone ::= 27
id-RICindicationTypeVone						ProtocolIE-ID-Vone ::= 28
id-RICrequestIDVone								ProtocolIE-ID-Vone ::= 29
id-RICsubscriptionDetailsVone					ProtocolIE-ID-Vone ::= 30
id-TimeToWaitVone								ProtocolIE-ID-Vone ::= 31
id-RICcontrolOutcomeVone						ProtocolIE-ID-Vone ::= 32
id-E2nodeComponentConfigUpdateVone				ProtocolIE-ID-Vone ::= 33
id-E2nodeComponentConfigUpdateVone-Item			ProtocolIE-ID-Vone ::= 34
id-E2nodeComponentConfigUpdateAckVone			ProtocolIE-ID-Vone ::= 35
id-E2nodeComponentConfigUpdateAckVone-Item		ProtocolIE-ID-Vone ::= 36
id-E2connectionSetup						ProtocolIE-ID-Vone ::= 39
id-E2connectionSetupFailed					ProtocolIE-ID-Vone ::= 40
id-E2connectionSetupFailed-Item-Vone				ProtocolIE-ID-Vone ::= 41
id-E2connectionFailed-Item					ProtocolIE-ID-Vone ::= 42
id-E2connectionUpdateVone-Item					ProtocolIE-ID-Vone ::= 43
id-E2connectionUpdateAdd					ProtocolIE-ID-Vone ::= 44
id-E2connectionUpdateModify					ProtocolIE-ID-Vone ::= 45
id-E2connectionUpdateRemove					ProtocolIE-ID-Vone ::= 46
id-E2connectionUpdateRemove-Item-Vone			ProtocolIE-ID-Vone ::= 47
id-TNLinformationVone							ProtocolIE-ID-Vone ::= 48

END

-- **************************************************************
--
-- Container definitions
--
-- derived from 3GPP 38.413 v15.4.0
-- **************************************************************

E2AP-Containers {
iso(1) identified-organization(3) dod(6) internet(1) private(4) enterprise(1) 53148 e2(1) version1 (1) e2ap(1) e2ap-Containers (5) }

DEFINITIONS AUTOMATIC TAGS ::=

BEGIN

-- **************************************************************
--
-- IE parameter types from other modules.
--
-- **************************************************************

IMPORTS

	CriticalityVone,
	PresenceVone,
	PrivateIE-ID,
	ProtocolExtensionID,
	ProtocolIE-ID-Vone
FROM E2AP-CommonDataTypes

	maxProtocolIEsVone
FROM E2AP-Constants;

-- **************************************************************
--
-- Class Definition for Protocol IEs
--
-- **************************************************************

E2AP-PROTOCOL-IES-VONE ::= CLASS {
	&id				ProtocolIE-ID-Vone					UNIQUE,
	&criticality	CriticalityVone,
	&Value,
	&presence		PresenceVone
}
WITH SYNTAX {
	ID				&id
	CRITICALITY		&criticality
	TYPE			&Value
	PRESENCE		&presence
}

-- **************************************************************
--
-- Class Definition for Protocol IEs
--
-- **************************************************************

E2AP-PROTOCOL-IES-VONE-PAIR ::= CLASS {
	&id					ProtocolIE-ID-Vone				UNIQUE,
	&firstCriticality	CriticalityVone,
	&FirstValue,
	&secondCriticality	CriticalityVone,
	&SecondValue,
	&presence			PresenceVone
}
WITH SYNTAX {
	ID						&id
	FIRST CRITICALITY		&firstCriticality
	FIRST TYPE				&FirstValue
	SECOND CRITICALITY		&secondCriticality
	SECOND TYPE				&SecondValue
	PRESENCE				&presence
}




-- **************************************************************
--
-- Container for Protocol IEs
--
-- **************************************************************

ProtocolIE-Container {E2AP-PROTOCOL-IES-VONE : IEsSetParam} ::= 
	SEQUENCE (SIZE (0..maxProtocolIEsVone)) OF
	ProtocolIE-Field {{IEsSetParam}}

ProtocolIE-SingleContainer {E2AP-PROTOCOL-IES-VONE : IEsSetParam} ::= 
	ProtocolIE-Field {{IEsSetParam}}

ProtocolIE-Field {E2AP-PROTOCOL-IES-VONE : IEsSetParam} ::= SEQUENCE {
	id				E2AP-PROTOCOL-IES-VONE.&id				({IEsSetParam}),
	criticality		E2AP-PROTOCOL-IES-VONE.&criticality		({IEsSetParam}{@id}),
	value			E2AP-PROTOCOL-IES-VONE.&Value			({IEsSetParam}{@id})
}

-- **************************************************************
--
-- Container for Protocol IE Pairs
--
-- **************************************************************

ProtocolIE-ContainerPair {E2AP-PROTOCOL-IES-VONE-PAIR : IEsSetParam} ::= 
	SEQUENCE (SIZE (0..maxProtocolIEsVone)) OF
	ProtocolIE-FieldPair {{IEsSetParam}}

ProtocolIE-FieldPair {E2AP-PROTOCOL-IES-VONE-PAIR : IEsSetParam} ::= SEQUENCE {
	id					E2AP-PROTOCOL-IES-VONE-PAIR.&id					({IEsSetParam}),
	firstCriticality	E2AP-PROTOCOL-IES-VONE-PAIR.&firstCriticality	({IEsSetParam}{@id}),
	firstValue			E2AP-PROTOCOL-IES-VONE-PAIR.&FirstValue			({IEsSetParam}{@id}),
	secondCriticality	E2AP-PROTOCOL-IES-VONE-PAIR.&secondCriticality	({IEsSetParam}{@id}),
	secondValue			E2AP-PROTOCOL-IES-VONE-PAIR.&SecondValue			({IEsSetParam}{@id})
}

-- **************************************************************
--
-- Container Lists for Protocol IE Containers
--
-- **************************************************************

ProtocolIE-ContainerList {INTEGER : lowerBound, INTEGER : upperBound, E2AP-PROTOCOL-IES-VONE : IEsSetParam} ::=
	SEQUENCE (SIZE (lowerBound..upperBound)) OF
	ProtocolIE-SingleContainer {{IEsSetParam}}

ProtocolIE-ContainerPairList {INTEGER : lowerBound, INTEGER : upperBound, E2AP-PROTOCOL-IES-VONE-PAIR : IEsSetParam} ::=
	SEQUENCE (SIZE (lowerBound..upperBound)) OF
	ProtocolIE-ContainerPair {{IEsSetParam}}


END
